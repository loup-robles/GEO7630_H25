FME workspace lab4_results.fmw

Parameters:
- SourceDataset_PNGRASTER = C:\Users\glogowski_C\Documents\Lab 4\hm-2002-can-4000-0257_georeferenced.png   # Source PNG (Portable Network Graphics) File(s)
- SourceDataset_COG_3 = C:\Users\glogowski_C\Documents\Lab 4\MNS(terrain+batiment)_2015_1m_Ville-Marie.tif   # Source GeoTIFF File(s) or URL(s)
- SourceDataset_COG = C:\Users\glogowski_C\Documents\Lab 4\ilots-de-chaleur-2016.tif   # Source GeoTIFF File(s) or URL(s)
- DestDataset_POSTGIS = Geo7630   # Connection

Readers:
- PNGRASTER_1: PNGRASTER from $(SourceDataset_PNGRASTER)
- COG_1: COG from $(SourceDataset_COG)
- COG_2: COG from $(SourceDataset_COG_3)

Writers:
- POSTGIS_1: POSTGIS to $(DestDataset_POSTGIS)

SQLExecutor__Rejected__Logged: Logger
    LOG_FEATURE = LOG_ONLY
    MAXCOORDS = 20
    MAXFEATS = 20
    MESSAGE = Feature is:
    SEVERITY = INFO

Bookmark: Image aérienne - Ville Marie
PNGRASTER (reader PNGRASTER_1)
    -> Reprojector
Note: Reprojector
Reprojector
    DEST = EPSG:32188
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> RasterPropertyExtractor
Note: On va chercher les métadonnées
RasterPropertyExtractor
    -> RasterResampler
Note: Réduction de la taille du raster pour stockage in memory
RasterResampler
    COLUMNS = @Value(_num_columns)/10
    INTERPOLATION_TYPE = NearestNeighbor
    ROWCOL_OR_CELLSIZE = RowsColumns
    ROWS = @Value(_num_rows)/10
    INTERPOLATION_TYPE_NAME = Nearest Neighbor
    RESAMPLED -> RasterPyramider
Note: Génère des images de taille plus petite pour affichage en fonction des niveaux de zoom si on veut l'afficher dans une application
RasterPyramider
    INTERPOLATION_TYPE_NAME_LOOKUP = NearestNeighbor
    NUMBER_OF_LEVELS = 10
    NUM_PYRAMID_LEVELS_ATTRIBUTE = _num_pyramid_levels
    PYRAMID_LEVEL_ATTRIBUTE = _pyramid_level
    RASTER_INDEX_ATTRIBUTE = _raster_index
    SMALLESTSIZE_OR_NUMLEVELS = Number of Levels
    USE_POWERS_OF_TWO = No
    INTERPOLATION_TYPE_NAME = Nearest Neighbor
    USE_POWERS_OF_TWO_LOOKUP = No
    PYRAMIDS -> FeatureWriter [Pyramids]
Note: FeatureWriter
FeatureWriter
    DATASET = Geo7630
    DATASET_ATTR = _dataset
    FEATURE_TYPE_LIST_ATTR = _feature_types
    FORMAT = POSTGIS_RASTER
    POSTGIS_RASTER_BULK_COPY = YES
    POSTGIS_RASTER_COORDINATE_SYSTEM_GRANULARITY = FEATURE_TYPE
    POSTGIS_RASTER_LOWERCASE_ATTRIBUTE_NAMES = Yes
    POSTGIS_RASTER_NAMED_CONNECTION = Geo7630
    POSTGIS_RASTER_SPATIAL_COLUMN_NAME = rast
    POSTGIS_RASTER_START_TRANSACTION = 0
    POSTGIS_RASTER_STRICT_TEMPORAL_TYPE_HANDLING = Yes
    POSTGIS_RASTER_TRANSACTION_INTERVAL = 100
    TOTAL_FEATURES_WRITTEN_ATTR = _total_features_written
    SUMMARY -> SQLExecutor [INITIATOR]
Note: SQLExecutor
SQLExecutor
    COMBINE_ATTRS = Result Attributes Only
    COMBINE_GEOM = Initiator Geometry Only
    DATASET = Geo7630
    FORMAT = POSTGIS_RASTER
    OUTPUT_FEATURES = DATA_ONLY
    POSTGIS_RASTER_NAMED_CONNECTION = Geo7630
    POSTGIS_RASTER_QUERY_FEATURE_TYPES_FOR_MERGE_FILTERS = Yes
    POSTGIS_RASTER_READER_META_ATTRIBUTES = fme_basename
    POSTGIS_RASTER_READ_TIME_WITH_TIMEZONE = Yes
    SQL_STATEMENT = CREATE TABLE public.mns_pyramid_2 AS SELECT * FROM hm-2002-can-4000-0257_pyramide WHERE pyramid_level = 2
    <REJECTED> -> SQLExecutor__Rejected_
Note: SQLExecutor__Rejected_
Note: SQLExecutor__Rejected__Logged
SQLExecutor__Rejected_: Logger
    LOG_FEATURE = LOG_ONLY
    MAXCOORDS = 20
    MAXFEATS = 20
    MESSAGE = Feature is:
    SEVERITY = INFO
    LOGGED -> SQLExecutor__Rejected__Logged

Bookmark: MNS - Ville Marie - 1m res
COG (reader COG_2)
    -> ContourGenerator [POINTS/LINES]
Note: Génère les contours depuis le raster
ContourGenerator
    BREAKLINE_METHOD = Yes
    CONFORMING_TOLERANCE_LOOKUP = AUTO
    CONTOUR_INTERVAL = 25
    ELEV_ATTR = _elevation
    TOLERANCE = 0
    CONFORMING_TOLERANCE = Automatic
    CONTOURS -> Generalizer
    <REJECTED> -> ContourGenerator__Rejected_
Note: Simplifie par 10 le nbre de vertex
Generalizer
    ALG = Douglas
    PRESERVE = No
    PRESERVE_PATHS_LOOKUP = NO
    TOLERANCE = 10
    ALG_TEXT = Douglas (Generalize)
    PRESERVE_PATHS = No
    -> AreaBuilder
    <REJECTED> -> Generalizer__Rejected_
Note: Ligne to polygones
AreaBuilder
    ALLOW_CYCLES = No
    CHECK_CURVE_DIRECTION = No
    CONNECT_Z_MODE_LOOKUP = FIRST_WINS
    CONSIDER_NODE_ELEVATION_LOOKUP = NO
    DEAGGREGATE_INPUT = Deaggregate
    DONUT_CREATION = NO
    LINES_AS_SEGMENTS = No
    POLY_ACCUM_ATTRS_NAME = Use Attributes From One Feature
    SNAPTYPE = NONE
    CONNECT_Z_MODE = First Wins
    CONSIDER_NODE_ELEVATION = no
    SNAPTYPE_PARAM = None
    AREA -> mns_contour_polygones (writer POSTGIS_1)
    <REJECTED> -> AreaBuilder__Rejected_
mns_contour_polygones (writer POSTGIS_1)
    attributes: _elevation float8
AreaBuilder__Rejected_: Logger
    LOG_FEATURE = LOG_ONLY
    MAXCOORDS = 20
    MAXFEATS = 20
    MESSAGE = Feature is:
    SEVERITY = INFO
Generalizer__Rejected_: Logger
    LOG_FEATURE = LOG_ONLY
    MAXCOORDS = 20
    MAXFEATS = 20
    MESSAGE = Feature is:
    SEVERITY = INFO
ContourGenerator__Rejected_: Logger
    LOG_FEATURE = LOG_ONLY
    MAXCOORDS = 20
    MAXFEATS = 20
    MESSAGE = Feature is:
    SEVERITY = INFO

Bookmark: Raster analytique - Îlots de chaleurs
COG (reader COG_1)
    -> RasterToPolygonCoercer
    -> RasterDiffuser
    -> RasterCellCoercer
Note: Transforme le raster en polygones
RasterToPolygonCoercer
    EXTRACT_NODATA = No
    LABEL_ATTRIBUTE = classification
    PRESERVE_ATTRIBUTES_LOOKUP = YES
    EXTRACT_NODATA_LOOKUP = No
    PRESERVE_ATTRIBUTES = Yes
    POLYGONS -> ilots_chaleur_polygones (writer POSTGIS_1)
ilots_chaleur_polygones (writer POSTGIS_1)
    attributes: classification varchar
Note: Améliore la définition du raster
RasterDiffuser
    PRESERVE_BAND_INTERPRETATION = No
    SHARPENING_FACTOR = 3.0
    SHARPENING_FILTER_MODE = Fine
    SHARPENING_ITERATIONS = 5
    SHARPENED -> RasterCellValueRounder
Note: Simplifie la classifcation
RasterCellValueRounder
    PLACES = 1
    ROUND_TYPE = nearest
    -> RasterToPolygonCoercer_2
Note: Transforme le raster en polygones
RasterToPolygonCoercer_2
    EXTRACT_NODATA = No
    LABEL_ATTRIBUTE = classification
    PRESERVE_ATTRIBUTES_LOOKUP = YES
    EXTRACT_NODATA_LOOKUP = No
    PRESERVE_ATTRIBUTES = Yes
    POLYGONS -> ilots_chaleur_polygones_sharp (writer POSTGIS_1)
ilots_chaleur_polygones_sharp (writer POSTGIS_1)
    attributes: classification varchar
Note: Transforme les pixels en points
RasterCellCoercer
    CELL_GEOMETRY = Points
    EXTRACT_NODATA = No
    EXTRACT_VALUES_AS_ATTRIBUTES = No
    PRESERVE_ATT = YES
    CELL_GEOMETRY_LOOKUP = Points
    EXTRACT_BAND_VALUES_AS = Z Values
    EXTRACT_NODATA_LOOKUP = No
    PRESERVE_ATTRIBUTES = Yes
    -> ilots_chaleur_points (writer POSTGIS_1)
ilots_chaleur_points (writer POSTGIS_1)
