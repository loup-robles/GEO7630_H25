FME workspace csv2_geojson2postgis.fmw

Parameters:
- SourceDataset_CSV2 = https://donnees.montreal.ca/dataset/b89fd27d-4b49-461b-8e54-fa2b34a628c4/resource/64e28fe6-ef37-437a-972d-d1d3f1f7d891/download/arbres-publics.csv   # Source CSV (Comma Separated Value) File(s)
- SourceDataset_GEOJSON = https://donnees.montreal.ca/dataset/9797a946-9da8-41ec-8815-f6b276dec7e9/resource/6b313375-d9bc-4dc3-af8e-ceae3762ae6e/download/limites-administratives-agglomeration-nad83.geojson   # Source GeoJSON File or URL
- DestDataset_POSTGIS = Geo7630   # Connection

Readers:
- CSV2_1: CSV2 from $(SourceDataset_CSV2)
- GEOJSON_1: GEOJSON from $(SourceDataset_GEOJSON)

Writers:
- POSTGIS_1: POSTGIS to $(DestDataset_POSTGIS)

CSV (reader CSV2_1)
    attributes: INV_TYPE varchar(1), EMP_NO uint32, ARROND uint32, ARROND_NOM varchar(43), Rue varchar(63), Rue_cote varchar(2), No_civique uint32, Emplacement varchar(23), Sigle varchar(6), Essence_latin varchar(45), Essence_fr varchar(48), Essence_ang varchar(44), DHP real32, Date_Releve datetime, Date_Plantation datetime, LOCALISATION varchar(49), Localisation_code varchar(5), CODE_PARC varchar(8), NOM_PARC varchar(60), Rue_de varchar(53), Rue_a varchar(53), Distance_pave real32, Distance_ligne_rue varchar(14), Stationnement_jour varchar(4), Stationnement_heure varchar(11), District uint32, Arbre_remarquable varchar(1), Code_secteur uint32, Nom_secteur varchar(23), Coord_X x_coordinate,
      Coord_Y y_coordinate, Longitude real64, Latitude real64
    -> Reprojector
limites-administratives-agglomeration-nad83 (reader GEOJSON_1)
    attributes: CODEID int, NOM string, NOM_OFFICIEL string, CODEMAMH string, CODE_3C string, NUM int, ABREV string, TYPE string, COMMENT string, DATEMODIF string
    -> Reprojector_2
Reprojector_2
    DEST = EPSG:32188
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> PointOnAreaOverlayer [AREA]
PointOnAreaOverlayer
    DEAGGREGATE_INPUT = Yes
    OV_ATTR = _overlaps
    POLYS_FIRST = NO
    AREA -> AttributeManager
densite_arbres_quartiers (writer POSTGIS_1)
    attributes: densite_arbre float8, nom varchar, qte_arbres int8

Bookmark: Traitement pour assurance qualité
Reprojector
    DEST = EPSG:32188
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> AttributeFilter
AttributeFilter
    ATTR_NAME = Longitude
    ATTR_VALUES = <Empty>,<Missing>,<Null>,<Unfiltered>
    <UNFILTERED> -> PointOnAreaOverlayer [POINT]

Bookmark: Simplification et creation d'attributs
AttributeManager
    ATTR_TABLE:
      REMOVE CODEID (int64)
      REMOVE NOM_OFFICIEL (buffer)
      REMOVE CODEMAMH (buffer)
      REMOVE CODE_3C (buffer)
      REMOVE NUM (int64)
      REMOVE ABREV (buffer)
      REMOVE TYPE (buffer)
      REMOVE COMMENT (buffer)
      REMOVE DATEMODIF (buffer)
      RENAME_SET_VALUE _overlaps > qte_arbres (uint32)
    -> AttributeCreator
AttributeCreator
    ATTR_TABLE = SET_TO densite_arbre (real64) = @Evaluate(@Value(qte_arbres) / @Area())
    -> densite_arbres_quartiers (writer POSTGIS_1)
